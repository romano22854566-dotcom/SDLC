// ============================================================================
// Спецификация требований на языке SysML v2 (OMG Systems Modeling Language v2)
// Проект: Трекер здорового распорядка дня и полезных привычек (HabitFlow C++)
// Автор: Петкун Роман Юрьевич, группа 450503
// ============================================================================

package HabitTrackerRequirements {
    private import ScalarValues::*;

    // Базовое определение требования системы
    requirement def SystemRequirement {
        attribute id : String;
        attribute title : String;
        attribute status : String;
        attribute priority : String;
    }

    // Корневое требование системы
    requirement <'REQ-SYS-001'> HabitTrackerSystem : SystemRequirement {
        attribute :>> id = "REQ-SYS-001";
        attribute :>> title = "Автономная система трекинга здорового распорядка дня";
        attribute :>> status = "Утверждено";
        attribute :>> priority = "High";
        doc
        /*
         * Система должна предоставлять локальное десктопное приложение для контроля
         * ключевых факторов здорового образа жизни (сна, питания, гидратации,
         * двигательной активности и зрительного отдыха) с вычислением дисциплины и стриков.
         */
    }

    // ========================================================================
    // Функциональные требования (Functional Requirements)
    // ========================================================================
    package FunctionalRequirements {

        requirement <'REQ-FUNC-001'> DailyHabitTracking : HabitTrackerSystem {
            attribute id = "REQ-FUNC-001";
            attribute title = "Ежедневный учёт базовых привычек";
            doc
            /*
             * Система должна позволять пользователю выбирать произвольную календарную дату
             * и фиксировать выполнение нормативов по сну, трём приёмам пищи (завтрак, обед, ужин)
             * и регулярным зрительным перерывам от монитора.
             */
        }

        requirement <'REQ-FUNC-002'> WaterBalanceControl : HabitTrackerSystem {
            attribute id = "REQ-FUNC-002";
            attribute title = "Контроль водного баланса с инкрементным вводом";
            doc
            /*
             * Система должна поддерживать быстрый ввод объёма выпитой воды порциями
             * (+250 мл, +500 мл, произвольный ввод), отображать прогресс до нормы (2000 мл)
             * в виде графической шкалы и вычислять процент выполнения.
             */
        }

        requirement <'REQ-FUNC-003'> ActivityAndBreaks : HabitTrackerSystem {
            attribute id = "REQ-FUNC-003";
            attribute title = "Учёт прогулок и интервалов отдыха от монитора";
            doc
            /*
             * Система должна учитывать фактическое время прогулки на свежем воздухе
             * (в минутах, норма >= 30 мин) и количество соблюдённых интервалов
             * зрительного отдыха по технике 50/10 (50 мин работы / 10 мин отдыха).
             */
        }

        requirement <'REQ-FUNC-004'> DisciplineCalculation : HabitTrackerSystem {
            attribute id = "REQ-FUNC-004";
            attribute title = "Автоматический расчёт суточного процента дисциплины";
            doc
            /*
             * По нажатию кнопки сохранения система должна рассчитывать совокупный показатель
             * дисциплины за сутки как взвешенную сумму 5 показателей (сон, питание, вода,
             * прогулки, экранный отдых) и отображать цветовую дифференциацию.
             */
        }

        requirement <'REQ-FUNC-005'> StreakMonitoring : HabitTrackerSystem {
            attribute id = "REQ-FUNC-005";
            attribute title = "Подсчёт непрерывной серии выполнения (стрика)";
            doc
            /*
             * Система должна непрерывно рассчитывать текущую серию дней подряд, в которых
             * интегральный процент дисциплины достиг либо превысил установленный порог (>=80%),
             * и выводить стрик крупным индикатором на главном экране.
             */
        }

        requirement <'REQ-FUNC-006'> InteractiveCalendar : HabitTrackerSystem {
            attribute id = "REQ-FUNC-006";
            attribute title = "Интерактивный календарь и аналитика";
            doc
            /*
             * Система должна отображать календарную сетку месяца/недели с цветовым кодированием
             * (зелёный: >=80%, жёлтый: 50-79%, красный: <50%) и выводить средний % соблюдения
             * по каждой привычке отдельно.
             */
        }

        requirement <'REQ-FUNC-007'> CustomNormSettings : HabitTrackerSystem {
            attribute id = "REQ-FUNC-007";
            attribute title = "Настройка индивидуальных целевых норм";
            doc
            /*
             * Пользователь должен иметь возможность через графический диалог изменять
             * целевые нормативы сна (часы), воды (мл), прогулок (мин) и порог зачёта стрика (%).
             */
        }

        requirement <'REQ-FUNC-008'> LocalDataExportImport : HabitTrackerSystem {
            attribute id = "REQ-FUNC-008";
            attribute title = "Экспорт и резервное копирование статистики";
            doc
            /*
             * Система должна поддерживать выгрузку накопленной истории дисциплины
             * в структурированные форматы JSON и CSV для анализа и резервирования.
             */
        }
    }

    // ========================================================================
    // Требования к качеству обслуживания (Quality of Service - QoS)
    // ========================================================================
    package QualityRequirements {

        requirement <'REQ-PERF-001'> FastStartup : HabitTrackerSystem {
            attribute id = "REQ-PERF-001";
            attribute title = "Время холодного запуска";
            doc
            /*
             * Время от запуска исполняемого файла C++ до полной готовности GUI к вводу
             * данных должно составлять не более 1.0 секунды на типовом ПК.
             */
        }

        requirement <'REQ-PERF-002'> QuickDailyLogging : HabitTrackerSystem {
            attribute id = "REQ-PERF-002";
            attribute title = "Эргономика и скорость заполнения отчёта";
            doc
            /*
             * Пользовательский интерфейс должен обеспечивать возможность внесения всех
             * показателей за день менее чем за 60 секунд.
             */
        }

        requirement <'REQ-SEC-001'> LocalIsolation : HabitTrackerSystem {
            attribute id = "REQ-SEC-001";
            attribute title = "100% Локальная изолированность и приватность";
            doc
            /*
             * Приложение не должно совершать сетевых соединений или передавать
             * персональные данные во внешнюю сеть. Все данные хранятся локально в JSON.
             */
        }

        requirement <'REQ-REL-001'> DataPersistenceSafety : HabitTrackerSystem {
            attribute id = "REQ-REL-001";
            attribute title = "Атомарное сохранение и устойчивость к сбоям";
            doc
            /*
             * Запись в файл данных должна производиться атомарно с созданием временного
             * файла и заменой основного во избежание повреждения базы при аварийном завершении.
             */
        }
    }
}
